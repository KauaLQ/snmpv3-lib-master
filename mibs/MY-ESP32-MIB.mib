MY-ESP32-MIB DEFINITIONS ::= BEGIN

IMPORTS
    enterprises, Integer32
        FROM SNMPv2-SMI;

myEnterprise OBJECT IDENTIFIER ::= { enterprises 12345 }

myObjects OBJECT IDENTIFIER ::= { myEnterprise 1 }

myScalar OBJECT-TYPE
    SYNTAX      Integer32
    MAX-ACCESS  read-only
    STATUS      current
    DESCRIPTION "Meu teste com ESP32"
    ::= { myObjects 1 }

END
